ONEACCESS-SAT-MIB DEFINITIONS ::=
BEGIN

--------------------------------------------------------------------
-- Imports
--------------------------------------------------------------------
   IMPORTS
      DisplayString, MacAddress, TEXTUAL-CONVENTION
		   FROM SNMPv2-TC
      MODULE-IDENTITY, OBJECT-TYPE,Integer32,Unsigned32
         FROM SNMPv2-SMI
      MODULE-COMPLIANCE, OBJECT-GROUP
         FROM SNMPv2-CONF
      oacExpIMSat,oacMIBModules
         FROM ONEACCESS-GLOBAL-REG;

--------------------------------------------------------------------
-- Module Entity
--------------------------------------------------------------------
   oacSatMIBModule MODULE-IDENTITY
      LAST-UPDATED   "202407040000Z"
      ORGANIZATION   "OneAccess"
      CONTACT-INFO   "mib-support@ekinops.com"
      DESCRIPTION    "This MIB module describes sat objects."

      REVISION "202407040000Z"
      DESCRIPTION
         "Initial version."

      ::= { oacMIBModules 2000 }

--------------------------------------------------------------------
-- oacSatSessionTable
--------------------------------------------------------------------
   oacSatSessionTable OBJECT-TYPE
       SYNTAX       SEQUENCE OF SatSessionTableEntry
       MAX-ACCESS   not-accessible
       STATUS       current
       DESCRIPTION  
           "A table that contains information about sat sessions. 
           These sessions hold parameters that define a data stream."
       ::= { oacExpIMSat 1 }

   oacSatSessionTableEntry OBJECT-TYPE
       SYNTAX       SatSessionTableEntry
       MAX-ACCESS   not-accessible
       STATUS       current
       DESCRIPTION
           "Information about a specific sat session."
       INDEX       { oacSatSessionId }
       ::= { oacSatSessionTable 1 }

   SatSessionTableEntry ::=
       SEQUENCE {
          oacSatSessionId      Integer32,
          oacSatSessionName    DisplayString
       }

   oacSatSessionId OBJECT-TYPE
       SYNTAX       Integer32
       MAX-ACCESS   read-only
       STATUS       current
       DESCRIPTION  "Unique identifier of the sat session."
      ::= { oacSatSessionTableEntry 1 }

   oacSatSessionName OBJECT-TYPE
       SYNTAX       DisplayString
       MAX-ACCESS   read-only
       STATUS       current
       DESCRIPTION  "The name of the sat session linked to session id."
       ::= { oacSatSessionTableEntry 2 }

--------------------------------------------------------------------
-- oacSatMonitorTable
--------------------------------------------------------------------
   SatMonitorStateTC ::= TEXTUAL-CONVENTION
      STATUS     current
      DESCRIPTION
            "The state of monitor session. The meanings of the values are:
            init(0)    - this session is created.
            active(1)  - this session is in measurement-interval,
                         during which packets are sent.
            idle(2)    - this session is in idle-time,
                         during which no packets are sent.
            wait(3)    - repetition-time is over, 
                         the SAT engine will wait until for all sent packets 
                         a reply is received or the reply-timeout is over.
            stopped(4) - this session is stopped."
      SYNTAX  INTEGER {
                  init(0),
                  active(1),
                  idle(2),
                  wait(3),
                  stopped(4)
      }

   oacSatMonitorTable OBJECT-TYPE
       SYNTAX       SEQUENCE OF SatMonitorTableEntry
       MAX-ACCESS   not-accessible
       STATUS       current
       DESCRIPTION  "A table that contains information about sat monitor sessions.
                    This information shows the current state and config of the monitor"
       ::= { oacExpIMSat 2 }

   oacSatMonitorTableEntry OBJECT-TYPE
       SYNTAX       SatMonitorTableEntry
       MAX-ACCESS   not-accessible
       STATUS       current
       DESCRIPTION  "Information about a specific sat monitor session."
       INDEX       { oacSatMonitorSessionId }
       ::= { oacSatMonitorTable 1 }

   SatMonitorTableEntry ::=
       SEQUENCE {
          oacSatMonitorSessionId            Integer32,
          oacSatMonitorState                SatMonitorStateTC,
          oacSatMonitorStart                DisplayString,
          oacSatMonitorDuration             Integer32,
          oacSatMonitorMessagePeriod        Unsigned32,
          oacSatMonitorRepetitionPeriod     Unsigned32,
          oacSatMonitorMeasurementInterval  Unsigned32,
          oacSatNumberOfBins                Unsigned32,
          oacSatBinsDelayMin                Unsigned32,
          oacSatBinsDelayMax                Unsigned32,
          oacSatBinsJitterMin               Unsigned32,
          oacSatBinsJitterMax               Unsigned32
       }

   oacSatMonitorSessionId OBJECT-TYPE
       SYNTAX       Integer32
       MAX-ACCESS   not-accessible
       STATUS       current
       DESCRIPTION  "Unique identifier of the sat monitor session."
      ::= { oacSatMonitorTableEntry 1 }

   oacSatMonitorState OBJECT-TYPE
       SYNTAX       SatMonitorStateTC
       MAX-ACCESS   read-only
       STATUS       current
       DESCRIPTION  "The state of monitor session."
      ::= { oacSatMonitorTableEntry 2 }

   oacSatMonitorStart OBJECT-TYPE
       SYNTAX       DisplayString
       MAX-ACCESS   read-only
       STATUS       current
       DESCRIPTION  "Start of last repetition period of the monitor session."
      ::= { oacSatMonitorTableEntry 3 }

   oacSatMonitorDuration OBJECT-TYPE
       SYNTAX       Integer32
       MAX-ACCESS   read-only
       STATUS       current
       DESCRIPTION  "The duration of current repetition-period"
      ::= { oacSatMonitorTableEntry 4 }

   oacSatMonitorMessagePeriod OBJECT-TYPE
       SYNTAX       Unsigned32
       MAX-ACCESS   read-only
       STATUS       current
       DESCRIPTION  "The time between two sent packets."
      ::= { oacSatMonitorTableEntry 5 }

   oacSatMonitorRepetitionPeriod OBJECT-TYPE
       SYNTAX       Unsigned32
       MAX-ACCESS   read-only
       STATUS       current
       DESCRIPTION  "The length of every period."
      ::= { oacSatMonitorTableEntry 6 }

   oacSatMonitorMeasurementInterval OBJECT-TYPE
       SYNTAX       Unsigned32
       MAX-ACCESS   read-only
       STATUS       current
       DESCRIPTION  "The during packets are sent in message-period."
      ::= { oacSatMonitorTableEntry 7 }

   oacSatNumberOfBins OBJECT-TYPE
       SYNTAX       Unsigned32
       MAX-ACCESS   read-only
       STATUS       current
       DESCRIPTION  "The number of divisions between min and mix."
      ::= { oacSatMonitorTableEntry 8 }

   oacSatBinsDelayMin OBJECT-TYPE
       SYNTAX       Unsigned32
       MAX-ACCESS   read-only
       STATUS       current
       DESCRIPTION  "Bins delay minimum value."
      ::= { oacSatMonitorTableEntry 9 }

   oacSatBinsDelayMax OBJECT-TYPE
       SYNTAX       Unsigned32
       MAX-ACCESS   read-only
       STATUS       current
       DESCRIPTION  "Bins delay maximum value."
      ::= { oacSatMonitorTableEntry 10 }

   oacSatBinsJitterMin OBJECT-TYPE
       SYNTAX       Unsigned32
       MAX-ACCESS   read-only
       STATUS       current
       DESCRIPTION  "Bins jitter minimum value for jitter-pos or jitter-neg."
      ::= { oacSatMonitorTableEntry 11 }

   oacSatBinsJitterMax OBJECT-TYPE
       SYNTAX       Unsigned32
       MAX-ACCESS   read-only
       STATUS       current
       DESCRIPTION  "Bins jitter maximum value for jitter-pos or jitter-neg."
      ::= { oacSatMonitorTableEntry 12 }

--------------------------------------------------------------------
-- oacSatCurrentBinsTable
--------------------------------------------------------------------
   SatBinsAttributeTC ::= TEXTUAL-CONVENTION
      STATUS     current
      DESCRIPTION
            "Three sets of sat bins."
      SYNTAX  INTEGER {
                delay(0),
                jitter-pos(1),
                jitter-neg(2)
      }

   oacSatCurrentBinsTable OBJECT-TYPE
       SYNTAX       SEQUENCE OF SatCurrentBinsTableEntry
       MAX-ACCESS   not-accessible
       STATUS       current
       DESCRIPTION  "A table that contains current bins values for monitor sessions"
       ::= { oacExpIMSat 3 }

   oacSatCurrentBinsTableEntry OBJECT-TYPE
       SYNTAX       SatCurrentBinsTableEntry
       MAX-ACCESS   not-accessible
       STATUS       current
       DESCRIPTION  "Current bins values of a specific sat monitor session."
       INDEX       { oacSatCurrentBinsSessionId, oacSatCurrentBinsAttribute, oacSatCurrentBinsIndex }
       ::= { oacSatCurrentBinsTable 1 }

   SatCurrentBinsTableEntry ::=
       SEQUENCE {
          oacSatCurrentBinsSessionId           Integer32,
          oacSatCurrentBinsAttribute           SatBinsAttributeTC,
          oacSatCurrentBinsIndex               Integer32,
          oacSatCurrentBinsValue               Integer32
       }

   oacSatCurrentBinsSessionId OBJECT-TYPE
       SYNTAX       Integer32
       MAX-ACCESS   not-accessible
       STATUS       current
       DESCRIPTION  "Unique identifier of the sat monitor session."
      ::= { oacSatCurrentBinsTableEntry 1 }

   oacSatCurrentBinsAttribute OBJECT-TYPE
       SYNTAX       SatBinsAttributeTC
       MAX-ACCESS   not-accessible
       STATUS       current
       DESCRIPTION  "The set of sat bins."
      ::= { oacSatCurrentBinsTableEntry 2 }

   oacSatCurrentBinsIndex OBJECT-TYPE
       SYNTAX       Integer32
       MAX-ACCESS   not-accessible
       STATUS       current
       DESCRIPTION  "Current bin index for every set of bins. 
                     The first index is for binMin, the last index is for binMax,
                     number-of-bins index are between binMin and binMax"
      ::= { oacSatCurrentBinsTableEntry 3 }

   oacSatCurrentBinsValue OBJECT-TYPE
       SYNTAX       Integer32
       MAX-ACCESS   read-only
       STATUS       current
       DESCRIPTION  "Current bin value. The first value is binMin, the last is binMax,
                     number-of-bins values are between binMin and binMax"
      ::= { oacSatCurrentBinsTableEntry 4 }

--------------------------------------------------------------------
-- oacSatBinsLogTable
--------------------------------------------------------------------
   oacSatBinsLogTable OBJECT-TYPE
       SYNTAX       SEQUENCE OF SatBinsLogTableEntry
       MAX-ACCESS   not-accessible
       STATUS       current
       DESCRIPTION  "A table that contains a log of bins for most recent run of a monitor sessions"
       ::= { oacExpIMSat 4 }

   oacSatBinsLogTableEntry OBJECT-TYPE
       SYNTAX       SatBinsLogTableEntry
       MAX-ACCESS   not-accessible
       STATUS       current
       DESCRIPTION  "A log of bins for most recent run of a specific monitor sessions."
       INDEX       { oacSatBinsLogSessionId, oacSatBinsLogAttribute, oacSatBinsLogDate, oacSatBinsLogIndex }
       ::= { oacSatBinsLogTable 1 }

   SatBinsLogTableEntry ::=
       SEQUENCE {
          oacSatBinsLogSessionId           Integer32,
          oacSatBinsLogAttribute           SatBinsAttributeTC,
          oacSatBinsLogDate                Integer32,
          oacSatBinsLogIndex               Integer32,
          oacSatBinsLogValue               Integer32
       }

   oacSatBinsLogSessionId OBJECT-TYPE
       SYNTAX       Integer32
       MAX-ACCESS   not-accessible
       STATUS       current
       DESCRIPTION  "Unique identifier of the sat monitor session."
      ::= { oacSatBinsLogTableEntry 1 }

   oacSatBinsLogAttribute OBJECT-TYPE
       SYNTAX       SatBinsAttributeTC
       MAX-ACCESS   not-accessible
       STATUS       current
       DESCRIPTION  "The set of sat log bins."
      ::= { oacSatBinsLogTableEntry 2 }

   oacSatBinsLogDate OBJECT-TYPE
       SYNTAX       Integer32
       MAX-ACCESS   not-accessible
       STATUS       current
       DESCRIPTION  "The startDateTime of the repetition period.
                     This timestamp starts from 2000-01-01"
      ::= { oacSatBinsLogTableEntry 3 }

   oacSatBinsLogIndex OBJECT-TYPE
       SYNTAX       Integer32
       MAX-ACCESS   not-accessible
       STATUS       current
       DESCRIPTION  "Index for every set of log bins.
                     The first index is for binMin, the last index is for binMax,
                     number-of-bins index are between binMin and binMax"
      ::= { oacSatBinsLogTableEntry 4 }

   oacSatBinsLogValue OBJECT-TYPE
       SYNTAX       Integer32
       MAX-ACCESS   read-only
       STATUS       current
       DESCRIPTION  "Log bin value. The first value is binMin, the last is binMax,
                     number-of-bins values are between binMin and binMax"
      ::= { oacSatBinsLogTableEntry 5 }

END
