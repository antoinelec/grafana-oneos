ONEACCESS-BGP4V2-MIB DEFINITIONS ::= BEGIN

    IMPORTS
        OBJECT-TYPE, MODULE-IDENTITY, IpAddress,
        Integer32, Counter32, Gauge32
            FROM SNMPv2-SMI
        InetAddressType, InetAddress, InetPortNumber
            FROM INET-ADDRESS-MIB
        Bgp4V2AddressFamilyIdentifierTC, Bgp4V2SubsequentAddressFamilyIdentifierTC
            FROM BGP4V2-TC-MIB
        oacVrfid
            FROM ONEACCESS-VRF-MIB
        oacExpIMIpRouting
            FROM ONEACCESS-GLOBAL-REG;

    oacbgp4V2 MODULE-IDENTITY
        LAST-UPDATED "202409230000Z"
        ORGANIZATION "OneAccess"
        CONTACT-INFO "support@ekinops.com"
        DESCRIPTION
          "This MIB module lists all BGP PEERs and counters belonging to different VRF"

	::= { oacExpIMIpRouting 2 }

--
-- Node definitions
--

    oacbgp4V2PeerTable OBJECT-TYPE
        SYNTAX     SEQUENCE OF OacBgp4V2PeerEntry
        MAX-ACCESS not-accessible
        STATUS     current
        DESCRIPTION
                "BGP peer table.  This table contains,
                 one entry per BGP peer, information about the
                 connections with BGP peers."
        ::= { oacbgp4V2 1 }
 
    oacbgp4V2PeerEntry OBJECT-TYPE
        SYNTAX     OacBgp4V2PeerEntry
        MAX-ACCESS not-accessible
        STATUS     current
        DESCRIPTION
                "Entry containing information about the
                 connection with a BGP peer."
        INDEX { oacVrfid,oacbgp4V2PeerRemoteAddrType,oacbgp4V2PeerRemoteAddr }
        ::= { oacbgp4V2PeerTable 1 }
 
    OacBgp4V2PeerEntry ::= SEQUENCE {
            oacbgp4V2PeerRemoteAddrType
                InetAddressType,
            oacbgp4V2PeerRemoteAddr
                InetAddress,
            oacbgp4V2PeerIdentifier
                IpAddress,
            oacbgp4V2PeerState
                INTEGER,
            oacbgp4V2PeerAdminStatus
                INTEGER,
            oacbgp4V2PeerNegotiatedVersion
                Integer32,
            oacbgp4V2PeerLocalAddrType
                InetAddressType,
            oacbgp4V2PeerLocalAddr
                InetAddress,
            oacbgp4V2PeerLocalPort
                InetPortNumber,
            oacbgp4V2PeerRemotePort
                InetPortNumber,
            oacbgp4V2PeerRemoteAs
                Integer32,
            oacbgp4V2PeerInUpdates
                Counter32,
            oacbgp4V2PeerOutUpdates
                Counter32,
            oacbgp4V2PeerInTotalMessages
                Counter32,
            oacbgp4V2PeerOutTotalMessages
                Counter32,
            oacbgp4V2PeerLastError
                OCTET STRING,
            oacbgp4V2PeerFsmEstablishedTransitions
                Counter32,
            oacbgp4V2PeerFsmEstablishedTime
                Gauge32,
            oacbgp4V2PeerConnectRetryInterval
                Integer32,
            oacbgp4V2PeerHoldTime
                Integer32,
            oacbgp4V2PeerKeepAlive
                Integer32,
            oacbgp4V2PeerHoldTimeConfigured
                Integer32,
            oacbgp4V2PeerKeepAliveConfigured
                Integer32,
            oacbgp4V2PeerMinASOriginationInterval
                Integer32,
            oacbgp4V2PeerMinRouteAdvertisementInterval
                Integer32,
            oacbgp4V2PeerInUpdateElapsedTime
                Gauge32
            }

    oacbgp4V2PeerRemoteAddrType OBJECT-TYPE
       SYNTAX      InetAddressType
        MAX-ACCESS read-only
        STATUS     current
        DESCRIPTION
                "The remote IP address family of this entry's BGP
                 peer."
        ::= { oacbgp4V2PeerEntry 1 }

    oacbgp4V2PeerRemoteAddr OBJECT-TYPE
        SYNTAX     InetAddress
        MAX-ACCESS read-only
        STATUS     current
        DESCRIPTION
                "The remote IP address of this entry's BGP
                 peer."
        ::= { oacbgp4V2PeerEntry 2 }

    oacbgp4V2PeerIdentifier OBJECT-TYPE
        SYNTAX     IpAddress
        MAX-ACCESS read-only
        STATUS     current
        DESCRIPTION
                "The BGP Identifier of this entry's BGP peer.
                 This entry MUST be 0.0.0.0 unless the
                 oacbgp4V2PeerState is in the openconfirm or the
                 established state."
        REFERENCE
                "RFC 4271, Section 4.2, 'BGP Identifier'."
        ::= { oacbgp4V2PeerEntry 3 }
 
    oacbgp4V2PeerState OBJECT-TYPE
        SYNTAX     INTEGER {
                            idle(1),
                            connect(2),
                            active(3),
                            opensent(4),
                            openconfirm(5),
                            established(6)
                   }
        MAX-ACCESS read-only
        STATUS     current
        DESCRIPTION
                "The BGP peer connection state."
        REFERENCE
                "RFC 4271, Section 8.2.2."
        ::= { oacbgp4V2PeerEntry 4 }
 
    oacbgp4V2PeerAdminStatus OBJECT-TYPE
        SYNTAX     INTEGER {
                            stop(1),
                            start(2)
                   }
        MAX-ACCESS read-only
        STATUS     current
        DESCRIPTION
                "The desired state of the BGP connection.
                 A transition from 'stop' to 'start' will cause
                 the BGP Manual Start Event to be generated.
                 A transition from 'start' to 'stop' will cause
                 the BGP Manual Stop Event to be generated.
                 This parameter can be used to restart BGP peer
                 connections.  Care should be used in providing
                 write access to this object without adequate
                 authentication."
        REFERENCE
                "RFC 4271, Section 8.1.2."
        ::= { oacbgp4V2PeerEntry 5 }
 
    oacbgp4V2PeerNegotiatedVersion OBJECT-TYPE
        SYNTAX     Integer32
        MAX-ACCESS read-only
        STATUS     current
        DESCRIPTION
                "The negotiated version of BGP running between
                 the two peers.
 
                 This entry MUST be zero (0) unless the
                 oacbgp4V2PeerState is in the openconfirm or the
 
 
 
                 established state.
 
                 Note that legal values for this object are
                 between 0 and 255."
        REFERENCE
                "RFC 4271, Section 4.2.
                 RFC 4271, Section 7."
        ::= { oacbgp4V2PeerEntry 6 }
 
    oacbgp4V2PeerLocalAddrType OBJECT-TYPE
        SYNTAX     InetAddressType
        MAX-ACCESS read-only
        STATUS     current
        DESCRIPTION
                "The local IP address of this entry's BGP
                 connection."
        ::= { oacbgp4V2PeerEntry 7 }

    oacbgp4V2PeerLocalAddr OBJECT-TYPE
        SYNTAX     InetAddress
        MAX-ACCESS read-only
        STATUS     current
        DESCRIPTION
                "The local IP address of this entry's BGP
                 connection."
        ::= { oacbgp4V2PeerEntry 8 }
 
    oacbgp4V2PeerLocalPort OBJECT-TYPE
        SYNTAX     InetPortNumber
        MAX-ACCESS read-only
        STATUS     current
        DESCRIPTION
                "The local port for the TCP connection between
                 the BGP peers."
        ::= { oacbgp4V2PeerEntry 9 }
 
    oacbgp4V2PeerRemotePort OBJECT-TYPE
        SYNTAX     InetPortNumber
        MAX-ACCESS read-only
        STATUS     current
        DESCRIPTION
                "The remote port for the TCP connection
                 between the BGP peers.  Note that the
                 objects oacbgp4V2PeerLocalAddr,
                 oacbgp4V2PeerLocalPort, oacbgp4V2PeerRemoteAddr, and
                 oacbgp4V2PeerRemotePort provide the appropriate
                 reference to the standard MIB TCP
                 connection table."
        ::= { oacbgp4V2PeerEntry 10 }
 
    oacbgp4V2PeerRemoteAs OBJECT-TYPE
        SYNTAX     Integer32
        MAX-ACCESS read-only
        STATUS     current
        DESCRIPTION
                "The remote autonomous system number received in
                 the BGP OPEN message."
        REFERENCE
                "RFC 4271, Section 4.2."
        ::= { oacbgp4V2PeerEntry 11 }
 
    oacbgp4V2PeerInUpdates OBJECT-TYPE
        SYNTAX     Counter32
        MAX-ACCESS read-only
        STATUS     current
        DESCRIPTION
                "The number of BGP UPDATE messages
                 received on this connection."
        REFERENCE
                "RFC 4271, Section 4.3."
        ::= { oacbgp4V2PeerEntry 12 }
 
    oacbgp4V2PeerOutUpdates OBJECT-TYPE
        SYNTAX     Counter32
        MAX-ACCESS read-only
        STATUS     current
        DESCRIPTION
                "The number of BGP UPDATE messages
                 transmitted on this connection."
        REFERENCE
                "RFC 4271, Section 4.3."
        ::= { oacbgp4V2PeerEntry 13 }
 
    oacbgp4V2PeerInTotalMessages OBJECT-TYPE
        SYNTAX     Counter32
        MAX-ACCESS read-only
        STATUS     current
        DESCRIPTION
                "The total number of messages received
                 from the remote peer on this connection."
        REFERENCE
                "RFC 4271, Section 4."
        ::= { oacbgp4V2PeerEntry 14 }
 
    oacbgp4V2PeerOutTotalMessages OBJECT-TYPE
        SYNTAX     Counter32
        MAX-ACCESS read-only
        STATUS     current
        DESCRIPTION
                "The total number of messages transmitted to
                 the remote peer on this connection."
        REFERENCE
                "RFC 4271, Section 4."
        ::= { oacbgp4V2PeerEntry 15 }
 
    oacbgp4V2PeerLastError OBJECT-TYPE
        SYNTAX     OCTET STRING (SIZE (2))
        MAX-ACCESS read-only
        STATUS     current
        DESCRIPTION
                "The last error code and subcode seen by this
                 peer on this connection.  If no error has
                 occurred, this field is zero.  Otherwise, the
                 first byte of this two byte OCTET STRING
                 contains the error code, and the second byte
                 contains the subcode."
        REFERENCE
                "RFC 4271, Section 4.5."
        ::= { oacbgp4V2PeerEntry 16 }
 
    oacbgp4V2PeerFsmEstablishedTransitions OBJECT-TYPE
        SYNTAX     Counter32
        MAX-ACCESS read-only
        STATUS     current
        DESCRIPTION
                "The total number of times the BGP FSM
                 transitioned into the established state
                 for this peer."
        REFERENCE
                "RFC 4271, Section 8."
        ::= { oacbgp4V2PeerEntry 17 }
 
    oacbgp4V2PeerFsmEstablishedTime OBJECT-TYPE
        SYNTAX     Gauge32
        UNITS      "seconds"
        MAX-ACCESS read-only
        STATUS     current
        DESCRIPTION
                "This timer indicates how long (in
                 seconds) this peer has been in the
                 established state or how long
                 since this peer was last in the
                 established state.  It is set to zero when
                 a new peer is configured or when the router is
                 booted."
        REFERENCE
                "RFC 4271, Section 8."
        ::= { oacbgp4V2PeerEntry 18 }
 
    oacbgp4V2PeerConnectRetryInterval OBJECT-TYPE
        SYNTAX     Integer32 (1..65535)
        UNITS      "seconds"
        MAX-ACCESS read-only
        STATUS     current
        DESCRIPTION
                "Time interval (in seconds) for the
                 ConnectRetry timer.  The suggested value
                 for this timer is 120 seconds."
        REFERENCE
                "RFC 4271, Section 8.2.2.  This is the value used
                 to initialize the 'ConnectRetryTimer'."
        ::= { oacbgp4V2PeerEntry 19 }
 
    oacbgp4V2PeerHoldTime OBJECT-TYPE
        SYNTAX     Integer32  ( 0 | 3..65535 )
        UNITS      "seconds"
        MAX-ACCESS read-only
        STATUS     current
        DESCRIPTION
                "Time interval (in seconds) for the Hold
                 Timer established with the peer.  The
                 value of this object is calculated by this
                 BGP speaker, using the smaller of the
                 values in oacbgp4V2PeerHoldTimeConfigured and the
                 Hold Time received in the OPEN message.
 
                 This value must be at least three seconds
                 if it is not zero (0).
 
                 If the Hold Timer has not been established
                 with the peer this object MUST have a value
                 of zero (0).
 
                 If the oacbgp4V2PeerHoldTimeConfigured object has
                 a value of (0), then this object MUST have a
                 value of (0)."
        REFERENCE
                "RFC 4271, Section 4.2."
        ::= { oacbgp4V2PeerEntry 20 }
 
    oacbgp4V2PeerKeepAlive OBJECT-TYPE
        SYNTAX     Integer32 ( 0 | 1..21845 )
        UNITS      "seconds"
        MAX-ACCESS read-only
        STATUS     current
        DESCRIPTION
                "Time interval (in seconds) for the KeepAlive
                 timer established with the peer.  The value
                 of this object is calculated by this BGP
                 speaker such that, when compared with
                 oacbgp4V2PeerHoldTime, it has the same proportion
                 that oacbgp4V2PeerKeepAliveConfigured has,
                 compared with oacbgp4V2PeerHoldTimeConfigured.
 
                 If the KeepAlive timer has not been established
                 with the peer, this object MUST have a value
                 of zero (0).
 
                 If the of oacbgp4V2PeerKeepAliveConfigured object
                 has a value of (0), then this object MUST have
                 a value of (0)."
        REFERENCE
                "RFC 4271, Section 4.4."
        ::= { oacbgp4V2PeerEntry 21 }
 
    oacbgp4V2PeerHoldTimeConfigured OBJECT-TYPE
        SYNTAX     Integer32 ( 0 | 3..65535 )
        UNITS      "seconds"
        MAX-ACCESS read-only
        STATUS     current
        DESCRIPTION
                "Time interval (in seconds) for the Hold Time
                 configured for this BGP speaker with this
                 peer.  This value is placed in an OPEN
                 message sent to this peer by this BGP
                 speaker, and is compared with the Hold
                 Time field in an OPEN message received
                 from the peer when determining the Hold
                 Time (oacbgp4V2PeerHoldTime) with the peer.
                 This value must not be less than three
                 seconds if it is not zero (0).  If it is
                 zero (0), the Hold Time is NOT to be
                 established with the peer.  The suggested
                 value for this timer is 90 seconds."
        REFERENCE
                "RFC 4271, Section 4.2.
                 RFC 4271, Section 10."
        ::= { oacbgp4V2PeerEntry 22 }
 
    oacbgp4V2PeerKeepAliveConfigured OBJECT-TYPE
        SYNTAX     Integer32 ( 0 | 1..21845 )
        UNITS      "seconds"
        MAX-ACCESS read-only
        STATUS     current
        DESCRIPTION
                "Time interval (in seconds) for the
                 KeepAlive timer configured for this BGP
                 speaker with this peer.  The value of this
                 object will only determine the
                 KEEPALIVE messages' frequency relative to
                 the value specified in
                 oacbgp4V2PeerHoldTimeConfigured; the actual
                 time interval for the KEEPALIVE messages is
                 indicated by oacbgp4V2PeerKeepAlive.  A
                 reasonable maximum value for this timer
                 would be one third of that of
                 oacbgp4V2PeerHoldTimeConfigured.
                 If the value of this object is zero (0),
                 no periodical KEEPALIVE messages are sent
                 to the peer after the BGP connection has
                 been established.  The suggested value for
                 this timer is 30 seconds."
        REFERENCE
                "RFC 4271, Section 4.4.
                 RFC 4271, Section 10."
        ::= { oacbgp4V2PeerEntry 23 }
 
    oacbgp4V2PeerMinASOriginationInterval OBJECT-TYPE
        SYNTAX     Integer32 (1..65535)
        UNITS      "seconds"
        MAX-ACCESS read-only
        STATUS     current
        DESCRIPTION
                "Time interval (in seconds) for the
                 MinASOriginationInterval timer.
                 The suggested value for this timer is 15
                 seconds."
        REFERENCE
                "RFC 4271, Section 9.2.1.2.
                 RFC 4271, Section 10."
        ::= { oacbgp4V2PeerEntry 24 }
 
    oacbgp4V2PeerMinRouteAdvertisementInterval OBJECT-TYPE
        SYNTAX     Integer32 (1..65535)
        UNITS      "seconds"
        MAX-ACCESS read-only
        STATUS     current
        DESCRIPTION
                "Time interval (in seconds) for the
                 MinRouteAdvertisementInterval timer.
                 The suggested value for this timer is 30
                 seconds for EBGP connections and 5
                 seconds for IBGP connections."
        REFERENCE
                "RFC 4271, Section 9.2.1.1.
                 RFC 4271, Section 10."
        ::= { oacbgp4V2PeerEntry 25 }
 
    oacbgp4V2PeerInUpdateElapsedTime OBJECT-TYPE
        SYNTAX     Gauge32
        UNITS      "seconds"
        MAX-ACCESS read-only
        STATUS     current
        DESCRIPTION
                "Elapsed time (in seconds) since the last BGP
                 UPDATE message was received from the peer.
                 Each time oacbgp4V2PeerInUpdates is incremented,
                 the value of this object is set to zero (0)."
        REFERENCE
                "RFC 4271, Section 4.3.
                 RFC 4271, Section 8.2.2, Established state."
        ::= { oacbgp4V2PeerEntry 26 }


    oacbgp4V2PeerCountersTable OBJECT-TYPE
        SYNTAX     SEQUENCE OF OacBgp4V2PeerCountersEntry
        MAX-ACCESS not-accessible
        STATUS     current
        DESCRIPTION
                "BGP peer counters table.  This table contains,
                 one entry per VRF BGP peer counters' information."
        ::= { oacbgp4V2 2 }

    oacbgp4V2PeerCountersEntry OBJECT-TYPE
        SYNTAX     OacBgp4V2PeerCountersEntry
        MAX-ACCESS not-accessible
        STATUS     current
        DESCRIPTION
                "Entry containing information about the
                 counters of a BGP peer."
        INDEX { oacVrfid,oacbgp4V2PeerCountersRemoteAddrType,
                oacbgp4V2PeerCountersRemoteAddr,oacbgp4V2PeerCountersAddrFamilyAfi,
                oacbgp4V2PeerCountersAddrFamilySafi }
        ::= { oacbgp4V2PeerCountersTable 1 }

    OacBgp4V2PeerCountersEntry ::= SEQUENCE {
            oacbgp4V2PeerCountersRemoteAddrType
                InetAddressType,
            oacbgp4V2PeerCountersRemoteAddr
                InetAddress,
            oacbgp4V2PeerCountersAddrFamilyAfi
                Bgp4V2AddressFamilyIdentifierTC,
            oacbgp4V2PeerCountersAddrFamilySafi
                Bgp4V2SubsequentAddressFamilyIdentifierTC,
            oacbgp4V2PeerCountersInPrefixes
                Gauge32,
            oacbgp4V2PeerCountersOutPrefixes
                Gauge32
            }

    oacbgp4V2PeerCountersRemoteAddrType OBJECT-TYPE
        SYNTAX     InetAddressType
        MAX-ACCESS read-only
        STATUS     current
        DESCRIPTION
                "The remote IP address of this entry's BGP
                 peer."
        ::= { oacbgp4V2PeerCountersEntry 1 }

    oacbgp4V2PeerCountersRemoteAddr OBJECT-TYPE
        SYNTAX     InetAddress
        MAX-ACCESS read-only
        STATUS     current
        DESCRIPTION
                "The remote IP address of this entry's BGP
                 peer."
        ::= { oacbgp4V2PeerCountersEntry 2 }

    oacbgp4V2PeerCountersAddrFamilyAfi OBJECT-TYPE
        SYNTAX      Bgp4V2AddressFamilyIdentifierTC
        MAX-ACCESS  read-only
        STATUS      current
        DESCRIPTION
                "The Address family of this entry's BGP
                 peer."
        ::= { oacbgp4V2PeerCountersEntry 3 }

    oacbgp4V2PeerCountersAddrFamilySafi OBJECT-TYPE
        SYNTAX      Bgp4V2SubsequentAddressFamilyIdentifierTC
        MAX-ACCESS  read-only
        STATUS      current
        DESCRIPTION
                "The Sub-address family of this entry's BGP
                 peer."
        ::= { oacbgp4V2PeerCountersEntry 4 }

    oacbgp4V2PeerCountersInPrefixes OBJECT-TYPE
        SYNTAX      Gauge32
        MAX-ACCESS  read-only
        STATUS      current
        DESCRIPTION
                "The number of prefixes received from the BGP
                 peer."
        ::= { oacbgp4V2PeerCountersEntry 5 }

    oacbgp4V2PeerCountersOutPrefixes OBJECT-TYPE
        SYNTAX      Gauge32
        MAX-ACCESS  read-only
        STATUS      current
        DESCRIPTION
                "The number of prefixes sent out to the BGP
                 peer."
        ::= { oacbgp4V2PeerCountersEntry 6 }

END

---
