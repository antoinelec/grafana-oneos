-- *****************************************************************
-- SFP MIB
-- *****************************************************************

ONEACCESS-SFP-MIB DEFINITIONS ::= BEGIN

IMPORTS
    MODULE-IDENTITY,  OBJECT-TYPE,  NOTIFICATION-TYPE, Integer32, TimeTicks     FROM SNMPv2-SMI
    Float32TC,  Float64TC,  Float128TC            FROM FLOAT-TC-MIB
        SnmpAdminString                       FROM SNMP-FRAMEWORK-MIB

MODULE-COMPLIANCE,  OBJECT-GROUP, 
    NOTIFICATION-GROUP                  FROM SNMPv2-CONF
    InterfaceIndex                      FROM IF-MIB
    oacExpInternalModules               FROM ONEACCESS-GLOBAL-REG;


oacExpIMSfp MODULE-IDENTITY
    LAST-UPDATED "202010050000Z"
    ORGANIZATION "Ekinops"
    CONTACT-INFO
        "pascal.kesteloot@oneaccess-net.com"
    DESCRIPTION
        "This MIB module describes the SFP Modules"
    ::= { oacExpInternalModules 969 }

--  The SFP MIB consists of the following groups:
--      SFP Information Table
--      SFP Diagnostic Table

oacSfpInfo      OBJECT IDENTIFIER ::= { oacExpIMSfp 1 }
oacSfpDiag      OBJECT IDENTIFIER ::= { oacExpIMSfp 2 }

-- Textual Conventions



-- ----------------------------------------------------
--
-- The SFP Information Table
--
-- ----------------------------------------------------

oacSfpInfoTable  OBJECT-TYPE
    SYNTAX  SEQUENCE OF OacSfpInfoEntry
    MAX-ACCESS          not-accessible
    STATUS              current
    DESCRIPTION
        "The SFP information table. 
        The table displays the parameters of the SFP-1310 and
        the SFP-WDM modules."
    ::= { oacSfpInfo 1 }

oacSfpInfoEntry OBJECT-TYPE
    SYNTAX  OacSfpInfoEntry
    MAX-ACCESS  not-accessible
    STATUS  current
    DESCRIPTION
        "An entry in the SFP information table.
        The index to this table is the same as the ifIndex of the SFP.
        The SFP Information Table contain and entry for each
        module of a type SFP."
    INDEX   { oacSfpInfoInterface }
    ::= { oacSfpInfoTable 1 }

OacSfpInfoEntry ::=
    SEQUENCE {
        oacSfpInfoInterface             InterfaceIndex, 

        -- Base ID Fields
        oacSfpInfoXcvrId                SnmpAdminString, 
        oacSfpInfo1310ExtXcvrId         INTEGER,
        oacSfpInfoConnectorCode         SnmpAdminString, 
        oacSfpInfoSonetOc123CCompliance SnmpAdminString, 
        oacSfpInfoSonetOc48Compliance   SnmpAdminString, 
        oacSfpInfoGbeCompliance         SnmpAdminString, 
        oacSfpInfoEncodingCode          SnmpAdminString, 
        oacSfpInfoNominalBitRate        SnmpAdminString, 
        oacSfpInfoFiberSpeed            SnmpAdminString, 
        oacSfpInfoFiberTxMedia          SnmpAdminString, 
        oacSfpInfoFiberTech             SnmpAdminString, 
        oacSfpInfoFiberLinkLen          SnmpAdminString,
        oacSfpInfoSingelFiberModeLength SnmpAdminString,
        oacSfpInfoLength50m10m          SnmpAdminString,
        oacSfpInfoLength62m10m          SnmpAdminString,
        oacSfpInfoLengthCopper1m        SnmpAdminString,
        oacSfpInfoVendorName            SnmpAdminString, 
        oacSfpInfoVendorOUI             SnmpAdminString, 
        oacSfpInfoVendorPN              SnmpAdminString, 
        oacSfpInfoVendorRev             SnmpAdminString, 
        oacSfpInfoWaveLength            SnmpAdminString,

        -- Extended ID Fields
        oacSfpInfoExtendedOptions       SnmpAdminString, 
        oacSfpInfoMaxBitRate            SnmpAdminString, 
        oacSfpInfoMinBitRate            SnmpAdminString, 
        oacSfpInfoVendorSN              SnmpAdminString, 
        oacSfpInfoDateCode              SnmpAdminString, 
        oacSfpInfoDiagnosticMonitoring  SnmpAdminString,
        oacSfpInfoOptionControlReg      SnmpAdminString, 
        oacSfpInfo8472Compliance        INTEGER, 

        -- XFP standard Fields
        oacSfpInfo10GbeCompliance       SnmpAdminString, 
        
        -- XFP SFP-8477 Extended Fields (Tuning and Dither)
        oacSfpInfoInternalCalibrationSupported  INTEGER
    }

oacSfpInfoInterface OBJECT-TYPE
    SYNTAX      InterfaceIndex
    MAX-ACCESS  read-only
    STATUS      current
    DESCRIPTION
        "The Interface Index of the SFP."
    ::= { oacSfpInfoEntry 1 }

-- Base ID Fields

oacSfpInfoXcvrId OBJECT-TYPE
    SYNTAX         SnmpAdminString  (SIZE (0..32))
    MAX-ACCESS  read-only
    STATUS      current
    DESCRIPTION
        "The identifier value specifies the physical device described by the serial information.
        This value shall be included in the serial data. The defined identifier values are:
            00h - Unknown or unspecified
            01h - GBIC
            02h - Module/connector soldered to motherboard
            03h - 1310 SFP 
            04-0Ah - Reserved for XFP and other platforms
            0Bh - DWDM SFP 
            80-FFh - Vendor specific."
    REFERENCE   "SFP-8472 Rev 2.3 Table 4-1 and 5-1, SFF-8024 Rev 4.7 Table 4-1"
    ::= { oacSfpInfoEntry 2 }

oacSfpInfo1310ExtXcvrId OBJECT-TYPE
    SYNTAX         INTEGER {
        modDef0(0),         -- GBIC definition is not specified or not compliant with a defined MOD_DEF
        modDef1(1),         -- GBIC is compliant with MOD_DEF 1
        modDef2(2),         -- GBIC is compliant with MOD_DEF 2
        modDef3(3),         -- GBIC is compliant with MOD_DEF 3
        modDef4(4),         -- GBIC/SFP function is defined by serial ID only
        modDef5(5),         -- GBIC is compliant with MOD_DEF 5
        modDef6(6),         -- GBIC is compliant with MOD_DEF 6
        modDef7(7)          -- GBIC is compliant with MOD_DEF 7
    }
    MAX-ACCESS  read-only
    STATUS      current          -- 1310
    DESCRIPTION
        "The extended identifier value provides additional information about the 1310 transceiver.
         The defined identifier values are:
            00h GBIC definition is not specified or the GBIC
                    definition is not compliant with a defined
                    MOD_DEF. See product specification for details.
            01h GBIC is compliant with MOD_DEF 1
            02h GBIC is compliant with MOD_DEF 2
            03h GBIC is compliant with MOD_DEF 3
            04h GBIC/SFP function is defined by serial ID only
            05h GBIC is compliant with MOD_DEF 5
            06h GBIC is compliant with MOD_DEF 6
            07h GBIC is compliant with MOD_DEF 7
            08-FFh Reserved"
    REFERENCE   "SFP-8472 Rev 2.3 Table 4-1 and 5-2"
    ::= { oacSfpInfoEntry 3 }

oacSfpInfoConnectorCode OBJECT-TYPE
    SYNTAX          SnmpAdminString  (SIZE (0..36))
    MAX-ACCESS  read-only
    STATUS      current
    DESCRIPTION
        "The identifier value specifies the physical device described by the serial information.
         The defined identifier values are:
            00h - Unknown or unspecified
            01h - SC
            02h - Fibre Channel Style 1 copper connector
            03h - Fibre Channel Style 2 copper connector 
            04h - BNC/TNC
            05h - Fibre Channel coaxial headers 
            06h - FiberJack 
            07h - LC 
            08h - MT-RJ 
            09h - MU 
            0Ah - SG 
            0Bh - Optical pigtail
            0Ch - 1Fh - Reserved 
            20h - HSSDC II 
            21h - Copper Pigtail
            22h - 7Fh - Reserved 
            80-FFh - Vendor specific."
    REFERENCE   "SFP-8472 Rev 2.3 Table 4-1 and SFF-8024 Rev 4.7 Table 4-3."
    ::= { oacSfpInfoEntry 4 }

oacSfpInfoSonetOc123CCompliance OBJECT-TYPE
    SYNTAX      SnmpAdminString  (SIZE (0..32))
    MAX-ACCESS  read-only
    STATUS      current
    DESCRIPTION
        "The following bit significant indicators define the SONET interfaces 
        that are supported by the transceiver. The defined identifier values are:
            Bits 6: OC-12,  single mode long reach
            Bits 5: OC-12,  single mode inter. reach
            Bits 4: OC-12 multi-mode short reach
            Bits 2: OC-3,  single mode long reach
            Bits 1: OC-3,  single mode inter. reach
            Bits 0: OC-3,  multi-mode short reach."
    REFERENCE   "SFP-8472 Rev 2.3 Table 4-1 and 5-3."
    ::= { oacSfpInfoEntry 5 }

oacSfpInfoSonetOc48Compliance OBJECT-TYPE
    SYNTAX       SnmpAdminString  (SIZE (0..26))
    MAX-ACCESS  read-only
    STATUS      current
    DESCRIPTION
        "The following bit significant indicators define the SONET OC-48interfaces 
        that are supported by the transceiver. The defined identifier values are:
            Bits 2: OC-48,  single mode long reach
            Bits 3: OC-48,  single mode inter. reach
            Bits 4: OC-48,  multi-mode short reach"
    REFERENCE   "SFP-8472 Rev 2.3 Table 4-1 and 5-3."
    ::= { oacSfpInfoEntry 6 }

oacSfpInfoGbeCompliance OBJECT-TYPE
    SYNTAX      SnmpAdminString  (SIZE (0..16))
    MAX-ACCESS  read-only
    STATUS      current
    DESCRIPTION
        "The following bit significant indicators define the Infiband interfaces 
        that are supported by the transceiver. The defined identifier values are:
            Bits 0: 1000BASE-SX
            Bits 1: 1000BASE-LX
            Bits 2: 1000BASE-CX
            Bits 3: 1000BASE-T
            Bits 4: 100BASE-LX/LX10        -- 1310
            Bits 5: 100BASE-FX             -- 1310
            Bits 6: BASE-BX10              -- 1310
            Bits 7: BASE-PX.               -- 1310"
    REFERENCE   "SFP-8472 Rev 2.3 Table 4-1 and 5-3"
    ::= { oacSfpInfoEntry 7 }


oacSfpInfoEncodingCode OBJECT-TYPE
    SYNTAX         SnmpAdminString  (SIZE (0..36))
    MAX-ACCESS  read-only
    STATUS      current
    DESCRIPTION
        "The encoding value indicates the serial encoding mechanism that is the 
        nominal design target of the particular transceiver. 
        The value shall be contained in the serial data. 
        The defined encoding values are:
            00h: Unspecified
            01h: 8B10B
            02h: 4B5B
            03h: NRZ
            04h: Manchester
            05h: SONET Scrambled
            06h -FFh: Reserved."
    REFERENCE   "SFP-8472 Rev 2.3 Table 4-1 and SFF-8024 Rev 4.7 Table 4-2 "
    ::= { oacSfpInfoEntry 8 }

oacSfpInfoNominalBitRate OBJECT-TYPE
    SYNTAX      SnmpAdminString  (SIZE (0..20))
    MAX-ACCESS  read-only
    STATUS      current
    DESCRIPTION
        "The nominal bit rate (BR,  nominal) is specified in units of 100 Megabits 
        per second,  rounded off to the nearest 100 Megabits per second. 
        The bit rate includes those bits necessary to encode and delimit the 
        signal as well as those bits carrying data information. 
        A value of 0 indicates that the bit rate is not specified and must be
        determined from the transceiver technology. 
        The actual information transfer rate will depend on the encoding of the data,  
        as defined by the encoding value."
    REFERENCE   "SFP-8472 Rev 2.3 Table 4-1."
    ::= { oacSfpInfoEntry 9 }

oacSfpInfoFiberSpeed  OBJECT-TYPE
    SYNTAX         SnmpAdminString  (SIZE (0..200))
    MAX-ACCESS  read-only
    STATUS      current
    DESCRIPTION
        "The following bits define the Fiber speed:
            Bits 0: 100 MBytes/Sec
            Bits 2: 200 MBytes/Sec
            Bits 3: 3200 MBytes/Sec
            Bits 4: 400 MBytes/Sec
            Bits 5: 1600 MBytes/Sec
            Bits 6: 800 MBytes/Sec
            Bits 7: 1200 MBytes/Sec"
    REFERENCE   "SFP-8472 Rev 2.3 Table 5-3."
    ::= { oacSfpInfoEntry 10 }

oacSfpInfoFiberTxMedia  OBJECT-TYPE
    SYNTAX         SnmpAdminString  (SIZE (0..20))
    MAX-ACCESS  read-only
    STATUS      current
    DESCRIPTION
        "The following bits define the Fiber Tx Media:
            Bits 0: Single Mode
            Bits 2: Multi-Mode, 50um
            Bits 3: Multi-Mode, 62.5um
            Bits 4: Video Coax
            Bits 5: Miniature Coax
            Bits 6: Twisted Pair
            Bits 7: Twin Axial Pair"
    REFERENCE   "SFP-8472 Rev 2.3 Table 5-3."
    ::= { oacSfpInfoEntry 11 }

oacSfpInfoFiberTech OBJECT-TYPE
    SYNTAX         SnmpAdminString  (SIZE (0..32))
    MAX-ACCESS  read-only
    STATUS      current
    DESCRIPTION
        "The following bits define the Fiber technology:
            A0h Octet 7 
            Bits 2: Copper Passive
                  Bits 3: Copper Active
            Bits 4: Longwave laser (LL)
            Bits 5: Shortwave laser w/ OFC
            Bits 6: Shortwave laser w/o OFC
            Bits 7: Electrical intra-enclosure
            A0 Octet 8 
            Bits 0: Electrical inter-enclosure
            Bits 1: Longwave laser (LC)
            Bits 2: Shortwave laser, linear Rx"
    REFERENCE   "SFP-8472 Rev 2.3 Table 5-3."
    ::= { oacSfpInfoEntry 12 }

oacSfpInfoFiberLinkLen  OBJECT-TYPE
    SYNTAX         SnmpAdminString  (SIZE (0..22))
    MAX-ACCESS  read-only
    STATUS      current
    DESCRIPTION
        "The following bits define the Fiber Link length.
            Bits 3: medium distance
            Bits 4: long distance
            Bits 5: intermediate distance
            Bits 6: short distance
            Bits 7: very long distance"
    REFERENCE   "SFP-8472 Rev 2.3 Table 4-1 and 5-3."
    ::= { oacSfpInfoEntry 13 }


oacSfpInfoSingelFiberModeLength OBJECT-TYPE
    SYNTAX      SnmpAdminString  (SIZE (0..20))
    MAX-ACCESS  read-only
    STATUS      current
    DESCRIPTION
        "This value specifies the link length that is supported by the transceiver while 
        operating in compliance with the applicable standards using single mode fiber. 
        A value of zero means that the transceiver does not support single mode 
        fiber or that the length information must be determined from the transceiver 
        technology."
    REFERENCE   "SFP-8472 Rev 2.3 Table 4-1."
    ::= { oacSfpInfoEntry 14 }

oacSfpInfoLength50m10m OBJECT-TYPE
    SYNTAX      SnmpAdminString  (SIZE (0..20))
    MAX-ACCESS  read-only
    STATUS      current      -- 1310
    DESCRIPTION
        "This value specifies the link length that is supported by the transceiver 
        while operating in compliance with the applicable standards using 50 micron 
        multi-mode fiber. 
        The value is in units of 10 meters. A value of 255 means that the transceiver 
        supports a link length greater than 2.54 km.
        A value of zero means that the transceiver does not support 50 micron 
        multimode fiber or that the length information must be determined from the 
        transceiver technology."
    REFERENCE   "SFP-8472 Rev 2.3 Table 4-1."
    ::= { oacSfpInfoEntry 15 }

oacSfpInfoLength62m10m OBJECT-TYPE
    SYNTAX      SnmpAdminString  (SIZE (0..20))
    MAX-ACCESS  read-only
    STATUS      current      -- 1310
    DESCRIPTION
        "This value specifies the link length that is supported by the transceiver 
        while operating in compliance with the applicable standards using 62.5 micron 
        multi-mode fiber. 
        The value is in units of 10 meters. A value of 255 means that the transceiver 
        supports a link length greater than 2.54 km.
        A value of zero means that the transceiver does not support 50 micron 
        multimode fiber or that the length information must be determined from the 
        transceiver technology.
        It is common for the transceiver to support both 50 micron and 62.5 micron 
        fiber."
    REFERENCE   "SFP-8472 Rev 2.3 Table 4-1."
    ::= { oacSfpInfoEntry 16 }

oacSfpInfoLengthCopper1m OBJECT-TYPE
    SYNTAX      SnmpAdminString  (SIZE (0..20))
    MAX-ACCESS  read-only
    STATUS      current      -- 1310
    DESCRIPTION
        "This value specifies the link length that is supported by the transceiver 
        while operating in compliance with the applicable standards using copper cable. 
        The value is in units of 1 meter. A value of 255 means that the transceiver 
        supports a link length greater than 254 meters.
        A value of zero means that the transceiver does not support copper cables 
        or that the length information must be determined from the 
        transceiver technology."
    REFERENCE   "SFP-8472 Rev 2.3 Table 4-1."
    ::= { oacSfpInfoEntry 17 }

oacSfpInfoVendorName OBJECT-TYPE
    SYNTAX      SnmpAdminString  (SIZE (0..16))
    MAX-ACCESS  read-only
    STATUS      current
    DESCRIPTION
        "The vendor name is a 16 character field that contains ASCII characters,  
        left-aligned and padded on the right with ASCII spaces (20h). 
        The vendor name shall be the full name of the corporation,  
        a commonly accepted abbreviation of the name of the corporation,  
        the SCSI company code for the corporation,  or the stock exchange code 
        for the corporation.
        At least one of the vendor name or the vendor OUI fields shall contain 
        valid serial data."
    REFERENCE   "SFP-8472 Rev 2.3 Table 4-1."
    ::= { oacSfpInfoEntry 18 }

oacSfpInfoVendorOUI OBJECT-TYPE
    SYNTAX      SnmpAdminString  (SIZE (0..12))
    MAX-ACCESS  read-only
    STATUS      current
    DESCRIPTION
        "The vendor organizationally unique identifier field (vendor OUI) 
        is a 3-byte field that contains the IEEE Company Identifier for the 
        vendor. A value of all zero in the 3-byte field indicates that 
        the Vendor OUI is unspecified."
    REFERENCE   "SFP-8472 Rev 2.3 Table 4-1."
    ::= { oacSfpInfoEntry 19 }

oacSfpInfoVendorPN OBJECT-TYPE
    SYNTAX      SnmpAdminString  (SIZE (0..16))
    MAX-ACCESS  read-only
    STATUS      current
    DESCRIPTION
        "The vendor part number (vendor PN) is a 16-byte field that contains 
        ASCII characters,  left-aligned and padded on the right with ASCII 
        spaces (20h),  defining the vendor part number or product name. 
        A value of all zero in the 16-byte field indicates that the
        vendor PN is unspecified."
    REFERENCE   "SFP-8472 Rev 2.3 Table 4-1."
    ::= { oacSfpInfoEntry 20 }

oacSfpInfoVendorRev OBJECT-TYPE
    SYNTAX      SnmpAdminString  (SIZE (0..16))
    MAX-ACCESS  read-only
    STATUS      current
    DESCRIPTION
        "The vendor revision number (vendor rev) is a 4-byte field that 
        contains ASCII characters,  left-aligned and padded on the right with 
        ASCII spaces (20h),  defining the vendor's product revision number. 
        A value of all zero in the 4-byte field indicates that
        the vendor PN is unspecified."
    REFERENCE   "SFP-8472 Rev 2.3 Table 4-1."
    ::= { oacSfpInfoEntry 21 }

oacSfpInfoWaveLength OBJECT-TYPE
    SYNTAX      SnmpAdminString  (SIZE (0..16))
    MAX-ACCESS  read-only
    STATUS      current
    DESCRIPTION
        "In the case of DWDM:
        Nominal transmitter output wavelength in units of 0.01nm.
        As an example,  a wavelength of 1550.51nm would be encoded as: 155051.
        In the case of 1310:
        The laser wavelength is equal to the the integer value in nm with 00 at
        the end.
        As an example,  a wavelength of 1310 would be encoded as: 131000."
    REFERENCE   "SFP-8472 Rev 2.3 Table 4-1."
    ::= { oacSfpInfoEntry 22 }

-- Extended ID Fields

oacSfpInfoExtendedOptions OBJECT-TYPE
    SYNTAX      SnmpAdminString  (SIZE (0..120))
    MAX-ACCESS  read-only
    STATUS      current
    DESCRIPTION
        "Specify the bitmap options implemented in the transceiver as described in.
        The bits definition is:
            5 RATE_SELECT is implemented
                NOTE: Lack of implemention does not indicate lack of
                simultaneous compliance with multiple standard rates.
                Compliance with particular standards should be determined
                from Transceiver Code.
            4 TX_DISABLE is implemented and disables the serial output.
            3 TX_FAULT signal implemented. (See SFP MSA)
            2 Loss of Signal implemented,  signal inverted from standard
                definition in SFP MSA.
                NOTE: This is not standard SFP/GBIC behavior and should
                be avoided,  since non-interoperable behavior results.
            1 Loss of Signal implemented,  signal as defined in SFP MSA."
    REFERENCE   "SFP-8472 Rev 2.3 Table 4-1 and 8-3."
    ::= { oacSfpInfoEntry 23 }

oacSfpInfoMaxBitRate OBJECT-TYPE
    SYNTAX      SnmpAdminString  (SIZE (0..20))
    MAX-ACCESS  read-only
    STATUS      current
    DESCRIPTION
        "The upper bit rate limit at which the transceiver will still meet its 
        specifications (BR,  max) is specified in units of 1% above the nominal 
        bit rate. 
        A value of zero indicates that this field is not specified."
    REFERENCE   "SFP-8472 Rev 2.3 Table 4-1."
    ::= { oacSfpInfoEntry 24 }

oacSfpInfoMinBitRate OBJECT-TYPE
    SYNTAX      SnmpAdminString  (SIZE (0..20))
    MAX-ACCESS  read-only
    STATUS      current
    DESCRIPTION
        "The lower bit rate limit at which the transceiver will still meet its 
        specifications (BR,  min) is specified in units of 1% below the nominal 
        bit rate. 
        A value of zero indicates that this field is not specified."
    REFERENCE   "SFP-8472 Rev 2.3 Table 4-1."
    ::= { oacSfpInfoEntry 25 }

oacSfpInfoVendorSN OBJECT-TYPE
    SYNTAX      SnmpAdminString  (SIZE (0..16))
    MAX-ACCESS  read-only
    STATUS      current
    DESCRIPTION
        "The vendor serial number (vendor SN) is a 16 character field that 
        contains ASCII characters,  left-aligned and padded on the right with 
        ASCII spaces (20h),  defining thevendor's serial number for the transceiver. 
        A value of all zero in the 16-byte field indicates that the vendor PN is 
        unspecified."
    REFERENCE   "SFP-8472 Rev 2.3 Table 4-1."
    ::= { oacSfpInfoEntry 26 }

oacSfpInfoDateCode OBJECT-TYPE
    SYNTAX      SnmpAdminString  (SIZE (8))
    MAX-ACCESS  read-only
    STATUS      current
    DESCRIPTION
        "The date code is an 6-byte field that contains the vendor's date 
        code in ASCII characters. The date code is mandatory. 
        The date code shall be in the format: <yy><mm><dd>."
    REFERENCE   "SFP-8472 Rev 2.3 Table 4-1 and 8-4."
    ::= { oacSfpInfoEntry 27 }

oacSfpInfoDiagnosticMonitoring OBJECT-TYPE
    SYNTAX      SnmpAdminString  (SIZE (0..80))
    MAX-ACCESS  read-only
    STATUS      current
    DESCRIPTION
        "A field with 8 single bit indicators which describe the
        optional digital diagnostic features implemented in the transceiver. 
        Since transceivers will not necessarily implement all optional 
        features described in this document,  the 'Enhanced Options' bit field 
        allows the host system to determine which functions are
        available over the 2 wire serial bus.
        The bits assignment is:
            6 Digital diagnostic monitoring implemented (described in this document). 
                Must be '1' for compliance with this document.
            5 Internally Calibrated
            4 Externally Calibrated"
   REFERENCE   "SFP-8472 Rev 2.3 Table 8-5."
    ::= { oacSfpInfoEntry 28 }

oacSfpInfoOptionControlReg OBJECT-TYPE
    SYNTAX      SnmpAdminString  (SIZE (0..230))
    MAX-ACCESS  read-only
    STATUS      current
    DESCRIPTION
        "A field with 8 single bit indicators which describe the
        optional and control features implemented in the transceiver. 
        The bits assignment is:
            7 TX Disable State 
            6 Soft TX Disable Select
            5 RS(1) State 
            4 Rate_Select State 
            3 Soft Rate_Select 
            2 TX Fault State
            1 Rx_LOS State 
            0 Data_Ready_Bar State"        
    REFERENCE   "SFP-8472 Rev 2.3 Table 9-11"
    ::= { oacSfpInfoEntry 29 }

oacSfpInfo8472Compliance OBJECT-TYPE
    SYNTAX      INTEGER {
        noDiag(0), 
        rev9-3(1), 
        rev9-5(2),
        rev10-2(3),
        rev10-4(4),
        rev11-0(5),
        rev11-3(6),
        rev11-4(7),
        rev12-3(8),
        unknown(255)
    }
    MAX-ACCESS  read-only
    STATUS      current
    DESCRIPTION
        "An unsigned integer that indicates which feature set(s) are
        implemented in the transceiver.
        The defined values are:
            0 - Digital diagnostic functionality not included or undefined.
            1 - Includes functionality described in Rev 9.3 SFF-8472.
            2 - Includes functionality described in Rev 9.5 SFF-8472.
            3 - Includes functionality described in Rev 10.2 SFF-8472.
            4 - Includes functionality described in Rev 10.4 SFF-8472.
            5 - Includes functionality described in Rev 11.0 SFF-8472.
            6 - Includes functionality described in Rev 11.3 SFF-8472.
            7 - Includes functionality described in Rev 11.4 SFF-8472.
            8 - Includes functionality described in Rev 12.3 SFF-8472.
                        9 to FF - Unallocated."
   REFERENCE   "SFP-8472 Rev 2.3 Table 8-8."
    ::= { oacSfpInfoEntry 30 }

--
-- XFP Information
--

oacSfpInfo10GbeCompliance OBJECT-TYPE
    SYNTAX      SnmpAdminString  (SIZE (0..16))
    MAX-ACCESS  read-only
    STATUS      current
    DESCRIPTION
        "The following bit significant indicators define the 10GbE interfaces 
        that are supported by the transceiver. The defined identifier values are:
            Bits  4: 10G Base-SR
            Bits  5: 10G Base-LR
            Bits  6: 10G Base-LRM
            Bits  7: 10G Base-ER."
    REFERENCE   "SFP-8472 Rev 2.3 Table 5-3."
    ::= { oacSfpInfoEntry 31 }

oacSfpInfoInternalCalibrationSupported OBJECT-TYPE
        SYNTAX      INTEGER {
            false(0), 
            true(1) 
        }
    MAX-ACCESS  read-only
    STATUS      current
    DESCRIPTION
        "This object checks if the internal calibration is supported."
    REFERENCE   "SFP-8472 Rev 2.3 Table 4-1 and 8-5."
    ::= { oacSfpInfoEntry 32 }    

-- ----------------------------------------------------
--
-- The SFP Diagnostic Table
--
-- ----------------------------------------------------

oacSfpDiagTable  OBJECT-TYPE
    SYNTAX  SEQUENCE OF OacSfpDiagEntry
    MAX-ACCESS          not-accessible
    STATUS              current
    DESCRIPTION
        "The SFP diagnostic table. 
        The table defines the status and control of the alarms and warnings
        of the SFP-1310 and the DWDM SFP-15xy modules."
    ::= { oacSfpDiag 1 }

oacSfpDiagEntry OBJECT-TYPE
    SYNTAX  OacSfpDiagEntry
    MAX-ACCESS  not-accessible
    STATUS  current
    DESCRIPTION
        "An entry in the SFP diagnostic table.
        The index to this table is the same as the ifIndex of the SFP.
        The SFP Diagnostic Table contain and entry for each
        SFP module."
    INDEX   { oacSfpDiagInterface }
    ::= { oacSfpDiagTable 1 }

OacSfpDiagEntry ::=
    SEQUENCE {
        oacSfpDiagInterface             InterfaceIndex, 

        -- Alarms and Warnings Thresholds
        oacSfpDiagHighTempAlmThreshold          SnmpAdminString, 
        oacSfpDiagLowTempAlmThreshold           SnmpAdminString, 
        oacSfpDiagHighTempWrnThreshold          SnmpAdminString, 
        oacSfpDiagLowTempWrnThreshold           SnmpAdminString, 
        oacSfpDiagHighVoltAlmThreshold          SnmpAdminString, 
        oacSfpDiagLowVoltAlmThreshold           SnmpAdminString, 
        oacSfpDiagHighVoltWrnThreshold          SnmpAdminString, 
        oacSfpDiagLowVoltWrnThreshold           SnmpAdminString, 
        oacSfpDiagHighTxBiasAlmThreshold        SnmpAdminString, 
        oacSfpDiagLowTxBiasAlmThreshold         SnmpAdminString, 
        oacSfpDiagHighTxBiasWrnThreshold        SnmpAdminString, 
        oacSfpDiagLowTxBiasWrnThreshold         SnmpAdminString, 
        oacSfpDiagHighTxPowerAlmThreshold       SnmpAdminString, 
        oacSfpDiagLowTxPowerAlmThreshold        SnmpAdminString, 
        oacSfpDiagHighTxPowerWrnThreshold       SnmpAdminString, 
        oacSfpDiagLowTxPowerWrnThreshold        SnmpAdminString, 
        oacSfpDiagHighRxPowerAlmThreshold       SnmpAdminString, 
        oacSfpDiagLowRxPowerAlmThreshold        SnmpAdminString, 
        oacSfpDiagHighRxPowerWrnThreshold       SnmpAdminString, 
        oacSfpDiagLowRxPowerWrnThreshold        SnmpAdminString, 
                
        -- Measured Values
        oacSfpDiagModuleTemperature             SnmpAdminString, 
        oacSfpDiagSupplyVoltage                 SnmpAdminString, 
        oacSfpDiagTxBias                        SnmpAdminString, 
        oacSfpDiagTxOutputPower                 SnmpAdminString, 
        oacSfpDiagRxInputPower                  SnmpAdminString, 

        -- Status and Control
        oacSfpDiagTempAlmWrn                    SnmpAdminString, 
        oacSfpDiagVccAlmWrn                     SnmpAdminString, 
        oacSfpDiagTxBiasAlmWrn                  SnmpAdminString, 
        oacSfpDiagTxPowerAlmWrn                 SnmpAdminString, 
        oacSfpDiagRxPowerAlmWrn                 SnmpAdminString
        
    }

oacSfpDiagInterface OBJECT-TYPE
    SYNTAX      InterfaceIndex
    MAX-ACCESS  read-only
    STATUS      current
    DESCRIPTION
        "The Interface Index of the SFP."
    ::= { oacSfpDiagEntry 1 }
-- Alarms and Warnings Thresholds

oacSfpDiagHighTempAlmThreshold OBJECT-TYPE
    SYNTAX      SnmpAdminString  (SIZE (0..20))
    MAX-ACCESS  read-only
    STATUS      current
    DESCRIPTION
        "The threshold value for high temperature alarm. The value 0
        means -128 Celsuis. An increment on one is equivalent to 1/256 degree, 
        yielding a total range of -128 to +128 Celsius."
    REFERENCE   "SFP-8472 Rev 2.3 Table 9-5."
    ::= { oacSfpDiagEntry 2 }

oacSfpDiagLowTempAlmThreshold OBJECT-TYPE
    SYNTAX      SnmpAdminString  (SIZE (0..20))
    MAX-ACCESS  read-only
    STATUS      current
    DESCRIPTION
        "The threshold value for low temperature alarm. The value 0
        means -128 Celsuis. An increment on one is equivalent to 1/256 degree, 
        yielding a total range of -128 to +128 Celsius.."
    REFERENCE   "SFP-8472 Rev 2.3 Table 9-5."
    ::= { oacSfpDiagEntry 3 }

oacSfpDiagHighTempWrnThreshold OBJECT-TYPE
    SYNTAX      SnmpAdminString  (SIZE (0..20))
    MAX-ACCESS  read-only
    STATUS      current
    DESCRIPTION
        "The threshold value for high temperature warning. The value 0
        means -128 Celsuis. An increment on one is equivalent to 1/256 degree, 
        yielding a total range of -128 to +128 Celsius."
    REFERENCE   "SFP-8472 Rev 2.3 Table 9-5."
    ::= { oacSfpDiagEntry 4 }

oacSfpDiagLowTempWrnThreshold OBJECT-TYPE
    SYNTAX      SnmpAdminString  (SIZE (0..20))
    MAX-ACCESS  read-only
    STATUS      current
    DESCRIPTION
        "The threshold value for low temperature warning. The value 0
        means -128 Celsuis. An increment on one is equivalent to 1/256 degree, 
        yielding a total range of -128 to +128 Celsius.."
    REFERENCE   "SFP-8472 Rev 2.3 Table 9-5."
    ::= { oacSfpDiagEntry 5 }

oacSfpDiagHighVoltAlmThreshold OBJECT-TYPE
    SYNTAX      SnmpAdminString  (SIZE (0..20))
    MAX-ACCESS  read-only
    STATUS      current
    DESCRIPTION
        "The threshold value for high voltage alarm. The value 0
        means 0 Volts. An increment on one is equivalent to 100 uVolt, 
        yielding a total range of +6.55 Volts."
    REFERENCE   "SFP-8472 Rev 2.3 Table 9-5."
    ::= { oacSfpDiagEntry 6 }

oacSfpDiagLowVoltAlmThreshold OBJECT-TYPE
    SYNTAX      SnmpAdminString  (SIZE (0..20))
    MAX-ACCESS  read-only
    STATUS      current
    DESCRIPTION
        "The threshold value for low voltage alarm. The value 0
        means 0 Volts. An increment on one is equivalent to 100 uVolt, 
        yielding a total range of +6.55 Volts."
    REFERENCE   "SFP-8472 Rev 2.3 Table 9-5."
    ::= { oacSfpDiagEntry 7 }

oacSfpDiagHighVoltWrnThreshold OBJECT-TYPE
    SYNTAX      SnmpAdminString  (SIZE (0..20))
    MAX-ACCESS  read-only
    STATUS      current
    DESCRIPTION
        "The threshold value for high voltage warning. The value 0
        means 0 Volts. An increment on one is equivalent to 100 uVolt, 
        yielding a total range of +6.55 Volts."
    REFERENCE   "SFP-8472 Rev 2.3 Table 9-5."
    ::= { oacSfpDiagEntry 8 }

oacSfpDiagLowVoltWrnThreshold OBJECT-TYPE
    SYNTAX      SnmpAdminString  (SIZE (0..20))
    MAX-ACCESS  read-only
    STATUS      current
    DESCRIPTION
        "The threshold value for low voltage warning. The value 0
        means 0 Volts. An increment on one is equivalent to 100 uVolt, 
        yielding a total range of +6.55 Volts."
    REFERENCE   "SFP-8472 Rev 2.3 Table 9-5."
    ::= { oacSfpDiagEntry 9 }

oacSfpDiagHighTxBiasAlmThreshold OBJECT-TYPE
    SYNTAX      SnmpAdminString  (SIZE (0..20))
    MAX-ACCESS  read-only
    STATUS      current
    DESCRIPTION
        "The threshold value for high voltage alarm. The value 0
        means 0 Volt. An increment on one is equivalent to 2 uA, 
        yielding a total range of 0 to 131 mA."
    REFERENCE   "SFP-8472 Rev 2.3 Table 9-5."
    ::= { oacSfpDiagEntry 10 }

oacSfpDiagLowTxBiasAlmThreshold OBJECT-TYPE
    SYNTAX      SnmpAdminString  (SIZE (0..20))
    MAX-ACCESS  read-only
    STATUS      current
    DESCRIPTION
        "The threshold value for low voltage alarm. The value 0
        means 0 Volts. An increment on one is equivalent to 2 uA, 
        yielding a total range of 0 to 131 mA."
    REFERENCE   "SFP-8472 Rev 2.3 Table 9-5."
    ::= { oacSfpDiagEntry 11 }

oacSfpDiagHighTxBiasWrnThreshold OBJECT-TYPE
    SYNTAX      SnmpAdminString  (SIZE (0..20))
    MAX-ACCESS  read-only
    STATUS      current
    DESCRIPTION
        "The threshold value for high voltage warning. The value 0
        means 0 Volt. An increment on one is equivalent to 2 uA, 
        yielding a total range of 0 to 131 mA."
    REFERENCE   "SFP-8472 Rev 2.3 Table 9-5."
    ::= { oacSfpDiagEntry 12 }

oacSfpDiagLowTxBiasWrnThreshold OBJECT-TYPE
    SYNTAX      SnmpAdminString  (SIZE (0..20))
    MAX-ACCESS  read-only
    STATUS      current
    DESCRIPTION
        "The threshold value for low voltage warning. The value 0
        means 0 Volts. An increment on one is equivalent to 2 uA, 
        yielding a total range of 0 to 131 mA."
    REFERENCE   "SFP-8472 Rev 2.3 Table 9-5."
    ::= { oacSfpDiagEntry 13 }

oacSfpDiagHighTxPowerAlmThreshold OBJECT-TYPE
    SYNTAX      SnmpAdminString  (SIZE (0..20))
    MAX-ACCESS  read-only
    STATUS      current
    DESCRIPTION
        "The threshold value for high TX power alarm. The value 0
        means 0 Volt. An increment on one is equivalent to 1 uW, 
        yielding a total range of 0 to 65.535 mW."
    REFERENCE   "SFP-8472 Rev 2.3 Table 9-5."
    ::= { oacSfpDiagEntry 14 }

oacSfpDiagLowTxPowerAlmThreshold OBJECT-TYPE
    SYNTAX      SnmpAdminString  (SIZE (0..20))
    MAX-ACCESS  read-only
    STATUS      current
    DESCRIPTION
        "The threshold value for low TX power alarm. The value 0
        means 0 Watts. An increment on one is equivalent to 0.1 uW, 
        yielding a total range of 0 to 65.535 mW."
    REFERENCE   "SFP-8472 Rev 2.3 Table 9-5."
    ::= { oacSfpDiagEntry 15 }

oacSfpDiagHighTxPowerWrnThreshold OBJECT-TYPE
    SYNTAX      SnmpAdminString  (SIZE (0..20))
    MAX-ACCESS  read-only
    STATUS      current
    DESCRIPTION
        "The threshold value for high TX power warning. The value 0
        means 0 Volt. An increment on one is equivalent to 1 uW, 
        yielding a total range of 0 to 65.535 mW."
    REFERENCE   "SFP-8472 Rev 2.3 Table 9-5."
    ::= { oacSfpDiagEntry 16 }

oacSfpDiagLowTxPowerWrnThreshold OBJECT-TYPE
    SYNTAX      SnmpAdminString  (SIZE (0..20))
    MAX-ACCESS  read-only
    STATUS      current
    DESCRIPTION
        "The threshold value for low TX power warning. The value 0
        means 0 Watts. An increment on one is equivalent to 0.1 uW, 
        yielding a total range of 0 to 65.535 mW."
    REFERENCE   "SFP-8472 Rev 2.3 Table 9-5."
    ::= { oacSfpDiagEntry 17 }

oacSfpDiagHighRxPowerAlmThreshold OBJECT-TYPE
    SYNTAX      SnmpAdminString  (SIZE (0..20))
    MAX-ACCESS  read-only
    STATUS      current
    DESCRIPTION
        "The threshold value for high RX power alarm. The value 0
        means 0 Watts. An increment on one is equivalent to 0.1 uW, 
        yielding a total range of 0 to 6.5535 mW."
    REFERENCE   "SFP-8472 Rev 2.3 Table 9-5."
    ::= { oacSfpDiagEntry 18 }

oacSfpDiagLowRxPowerAlmThreshold OBJECT-TYPE
    SYNTAX      SnmpAdminString  (SIZE (0..20))
    MAX-ACCESS  read-only
    STATUS      current
    DESCRIPTION
        "The threshold value for low RX power alarm. The value 0
        means 0 Volt. An increment on one is equivalent to 1 uW, 
        yielding a total range of 0 to 6.5535 mW."
    REFERENCE   "SFP-8472 Rev 2.3 Table 9-5."
    ::= { oacSfpDiagEntry 19 }

oacSfpDiagHighRxPowerWrnThreshold OBJECT-TYPE
    SYNTAX      SnmpAdminString  (SIZE (0..20))
    MAX-ACCESS  read-only
    STATUS      current
    DESCRIPTION
        "The threshold value for high RX power warning. The value 0
        means 0 Watts. An increment on one is equivalent to 0.1 uW, 
        yielding a total range of 0 to 6.5535 mW."
    REFERENCE   "SFP-8472 Rev 2.3 Table 9-5."
    ::= { oacSfpDiagEntry 20 }

oacSfpDiagLowRxPowerWrnThreshold OBJECT-TYPE
    SYNTAX      SnmpAdminString  (SIZE (0..20))
    MAX-ACCESS  read-only
    STATUS      current
    DESCRIPTION
        "The threshold value for low RX power warning. The value 0
        means 0 Volt. An increment on one is equivalent to 1 uW, 
        yielding a total range of 0 to 6.5535 mW."
    REFERENCE   "SFP-8472 Rev 2.3 Table 9-5."
    ::= { oacSfpDiagEntry 21 }


-- Diagnostics Measured Values

oacSfpDiagModuleTemperature OBJECT-TYPE
    SYNTAX      SnmpAdminString  (SIZE (0..20))
    MAX-ACCESS  read-only
    STATUS      current
    DESCRIPTION
        "Internally measured module temperature. The value 0 means -128 Celsuis. 
        An increment on one is equivalent to 1/256 degree, 
        yielding a total range of -128 to +128 Celsius. 
        Temperature accuracy is vendor specific but must be better than +/-3
        degrees Celsius over specified operating temperature and voltage."
    REFERENCE   "SFP-8472 Rev 2.3 Table 9-11."
    ::= { oacSfpDiagEntry 22 }

oacSfpDiagSupplyVoltage OBJECT-TYPE
    SYNTAX      SnmpAdminString  (SIZE (0..20))
    MAX-ACCESS  read-only
    STATUS      current
    DESCRIPTION
        "Internally measured supply voltage in transceiver. The value 0 means 0 Volts. 
        An increment on one is equivalent to 100 uVolt, 
        yielding a total range of +6.55 Volts.
        Accuracy is vendor specific but must be better than +/-3% of the
        manufacturer's nominal value over specified operating temperature and voltage."
    REFERENCE   "SFP-8472 Rev 2.3 Table 9-11."
    ::= { oacSfpDiagEntry 23 }

oacSfpDiagTxBias OBJECT-TYPE
    SYNTAX      SnmpAdminString  (SIZE (0..20))
    MAX-ACCESS  read-only
    STATUS      current
    DESCRIPTION
        "Internally measured TX Bias Current. The value 0
        means 0 Volt. An increment on one is equivalent to 2 uA, 
        yielding a total range of 0 to 131 mA.
        Accuracy is vendor specific but must be better than +/-3dB over specified 
        temperature and voltage. Data is not valid when the transmitter is disabled."
    REFERENCE   "SFP-8472 Rev 2.3 Table 9-11."
    ::= { oacSfpDiagEntry 24 }

oacSfpDiagTxOutputPower OBJECT-TYPE
    SYNTAX      SnmpAdminString  (SIZE (0..30))
    MAX-ACCESS  read-only
    STATUS      current
    DESCRIPTION
        "Measured TX output power. The value 0
        means 0 Watts. An increment on one is equivalent to 0.1 uW, 
        yielding a total range of 0 to 6.5535 mW.
        For the vendor specified wavelength,  accuracy shall be better than +/-3dB 
        over specified temperature and voltage."
    REFERENCE   "SFP-8472 Rev 2.3 Table 9-11."
    ::= { oacSfpDiagEntry 25 }

oacSfpDiagRxInputPower OBJECT-TYPE
    SYNTAX      SnmpAdminString  (SIZE (0..30))
    MAX-ACCESS  read-only
    STATUS      current         
    DESCRIPTION
        "Measured RX input power. The value 0
        means 0 Watts. An increment on one is equivalent to 0.1 uW, 
        yielding a total range of 0 to 6.5535 mW.
        For the vendor specified wavelength,  accuracy shall be better than +/-3dB 
        over specified temperature and voltage."
    REFERENCE   "SFP-8472 Rev 2.3 Table 9-11."
    ::= { oacSfpDiagEntry 26 }

-- Status and Control

oacSfpDiagTempAlmWrn OBJECT-TYPE
    SYNTAX  SnmpAdminString  (SIZE (0..100))
    MAX-ACCESS  read-only
    STATUS  current       
    DESCRIPTION
        "This object indicates the Alarms and Warnings for the temperature of the SFP module.  
        it can represent multiple failures (alarms and warnings) simultaneously."
    REFERENCE   "SFP-8472 Rev 2.3 Table 9-12."
     ::= { oacSfpDiagEntry 27 }

oacSfpDiagVccAlmWrn OBJECT-TYPE
    SYNTAX  SnmpAdminString  (SIZE (0..100))
    MAX-ACCESS  read-only
    STATUS  current       
    DESCRIPTION
        "This object indicates the Alarms and Warnings for the supply voltage of the SFP module.  
        it can represent multiple failures (alarms and warnings) simultaneously."
    REFERENCE   "SFP-8472 Rev 2.3 Table 9-12."
     ::= { oacSfpDiagEntry 28 }

oacSfpDiagTxBiasAlmWrn OBJECT-TYPE
    SYNTAX  SnmpAdminString  (SIZE (0..100))
    MAX-ACCESS  read-only
    STATUS  current       
    DESCRIPTION
        "This object indicates the Alarms and Warnings for the Tx Bias of the SFP module.  
        it can represent multiple failures (alarms and warnings) simultaneously."
    REFERENCE   "SFP-8472 Rev 2.3 Table 9-12."
     ::= { oacSfpDiagEntry 29 }

oacSfpDiagTxPowerAlmWrn OBJECT-TYPE
    SYNTAX  SnmpAdminString  (SIZE (0..100))
    MAX-ACCESS  read-only
    STATUS  current       
    DESCRIPTION
        "This object indicates the Alarms and Warnings for the Tx Powerof the SFP module.  
        it can represent multiple failures (alarms and warnings) simultaneously."
    REFERENCE   "SFP-8472 Rev 2.3 Table 9-12."
     ::= { oacSfpDiagEntry 30 }

oacSfpDiagRxPowerAlmWrn OBJECT-TYPE
    SYNTAX  SnmpAdminString  (SIZE (0..100))
    MAX-ACCESS  read-only
    STATUS  current       
    DESCRIPTION
        "This object indicates the Alarms and Warnings for the Rx Power of the SFP module.  
        it can represent multiple failures (alarms and warnings) simultaneously."
    REFERENCE   "SFP-8472 Rev 2.3 Table 9-12."
     ::= { oacSfpDiagEntry 31 }

END
